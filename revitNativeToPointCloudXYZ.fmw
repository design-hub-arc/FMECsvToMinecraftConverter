FME workspace revitNativeToPointCloudXYZ.fmw

Parameters:
- SourceDataset_REVITNATIVE = $(FME_MF_DIR)sourceData\revitData\DESGN100_Sample.rvt   # Revit Project File(s)
- DestDataset_POINTCLOUDXYZ = $(FME_MF_DIR)convertedData   # Destination Point Cloud XYZ Folder
- file_name = surfaces   # Enter file name to export as
- SourceDataset_REVITNATIVE_3 = $(FME_MF_DIR)sourceData\revitData\Copy of AEROSPACE MUSEUM .rvt   # Revit Project File(s)
- FEATURE_TYPES =
- DestDataset_CSV2 = $(FME_MF_DIR)convertedData   # Destination CSV (Comma Separated Value) Folder

Readers:
- REVITNATIVE_1: REVITNATIVE from $(SourceDataset_REVITNATIVE) in *XY-FT*
- REVITNATIVE_2: REVITNATIVE from $(SourceDataset_REVITNATIVE_3)

Writers:
- POINTCLOUDXYZ_1: POINTCLOUDXYZ to $(DestDataset_POINTCLOUDXYZ) in *XY-FT*
- CSV2_1: CSV2 to $(DestDataset_CSV2) in *XY-MT*

Metadata.FileInformation (reader REVITNATIVE_2)
    attributes: DocVer char(18), DocUpdate char(14), AuthorUsername char(0), CreatedBy char(14), CentralModelPath char(0), IsCentralModel boolean, IsCreatedLocally boolean, LevelElevationInfo.Level 1 number(31,15), LevelElevationInfo.Level 2 (Second Floor) number(31,15), LevelElevationInfo.Level 04 - T.O. Fnd. Wall number(31,15), LevelElevationInfo.Level 03 - T.O. Basement Slab number(31,15), LevelElevationInfo.Level 02 - T.O. Footing number(31,15), LevelElevationInfo.Level 01 - B.O. Footing number(31,15), LevelElevationInfo.Roof number(31,15), IdentityData.Author char(0), IdentityData.BuildingName char(0), IdentityData.OrganizationDescription char(0), IdentityData.OrganizationName char(0), Other.ClientName char(22), Other.ProjectAddress char(18), Other.ProjectIssueDate char(10), Other.ProjectName char(0), Other.ProjectNumber char(14), Other.ProjectStatus char(14), AnalyticalProperties.AnalyticConstruction char(32), AnalyticalProperties.ConstructionTypeId char(5), AnalyticalProperties.SolarHeatGainCoefficient number(31,15), AnalyticalProperties.VisualLightTransmittance number(31,15), BaseCategory char(10), BaseLevel char(7),
      BaseLevelElevation number(31,15), BaseLevelIsStory char(3), BaseLevelRoomOffset number(31,15), BuildingLevel char(7), BuildingLevelElevation number(31,15), BuildingLevelIsStory char(3), BuildingLevelRoomOffset number(31,15), Category char(10), Constraints.BaseExtensionDistance number(31,15), Constraints.BaseOffset number(31,15), Constraints.BaseOffsetFromLevel number(31,15), Constraints.CutoffOffset number(31,15), Constraints.DefaultElevation number(31,15), Constraints.HeightOffsetFromLevel number(31,15), Constraints.TopExtensionDistance number(31,15), Constraints.TopOffset number(31,15), Constraints.UnconnectedHeight number(31,15), Construction.AngledJoins number(10,0), Construction.BalusterOffset number(31,15), Construction.FasciaDepth number(31,15), Construction.FixtureType char(9), Construction.Function number(10,0), Construction.LandingHeightAdjustment number(31,15), Construction.MaximumRidgeHeight number(31,15), Construction.RafterCut number(10,0), Construction.RafterorTruss number(10,0), Construction.RailConnections number(10,0), Construction.RailingHeight number(31,15), Construction.ShowEndBracket boolean, Construction.ShowStartBracket boolean,
      Construction.TangentJoins number(10,0), Construction.TrimlessFlange boolean, Construction.TwoSided boolean, Construction.UseLandingHeightAdjustment boolean, Construction.WallClosure number(10,0), CreatedPhase char(18), DetailLevel char(6), Dimensions.BottomRail number(31,15), Dimensions.CosAng number(31,15), Dimensions.CounterThickness number(31,15), Dimensions.DefaultSillHeight number(31,15), Dimensions.Depth number(31,15), Dimensions.Diagonal number(31,15), Dimensions.Distance number(31,15), Dimensions.FountainLength number(31,15), Dimensions.FountainWidth number(31,15), Dimensions.H number(31,15), Dimensions.Height number(31,15), Dimensions.HoopSpace number(31,15), Dimensions.InsideDiameter number(31,15), Dimensions.InsideRadius number(31,15), Dimensions.L number(31,15), Dimensions.Length number(31,15), Dimensions.Offset number(31,15), Dimensions.OutsideDiameter number(31,15), Dimensions.PanelWidth number(31,15), Dimensions.RoomArea number(31,15), Dimensions.RoughHeight number(31,15), Dimensions.RoughWidth number(31,15), Dimensions.RungLength number(31,15),
      Dimensions.RungSpace number(31,15), Dimensions.SinAng number(31,15), Dimensions.Stiles number(31,15), Dimensions.Thickness number(31,15), Dimensions.TopOfCounter number(31,15), Dimensions.TopRail number(31,15), Dimensions.TrimProjection number(31,15), Dimensions.TrimProjectionExt number(31,15), Dimensions.TrimProjectionExt. number(31,15), Dimensions.TrimProjectionInt number(31,15), Dimensions.TrimProjectionInt. number(31,15), Dimensions.TrimWidth number(31,15), Dimensions.TrimWidthExt. number(31,15), Dimensions.TrimWidthInt. number(31,15), Dimensions.UrinalHeight number(31,15), Dimensions.UrinalLength number(31,15), Dimensions.UrinalWidth number(31,15), Dimensions.Width number(31,15), Dimensions.WindowInset number(31,15), Discipline char(13), ElementType char(15), Elevation number(31,15), Family char(0), FamilyType char(20), Function char(8), Graphics.Stand boolean, HostFeatureType char(28), HostId number(10,0), IdentityData.AssemblyCode char(0), IdentityData.AssemblyDescription char(23),
      IdentityData.Description char(0), IdentityData.Manufacturer char(0), IdentityData.Mark char(2), IdentityData.Model char(0), IdentityData.OmniclassNumber char(17), IdentityData.OmniclassTitle char(17), IdentityData.RoomName char(7), IdentityData.RoomNumber char(1), IdentityData.SectionNameKey char(6), IdentityData.TypeComments char(47), IdentityData.URL char(0), InExteriorShell char(3), IsTemplateView boolean, MaterialsandFinishes.BasinMaterial char(16), MaterialsandFinishes.BenchMaterial char(8), MaterialsandFinishes.BracketMaterial char(21), MaterialsandFinishes.CounterTopMaterial char(7), MaterialsandFinishes.DiffuserMaterial char(28), MaterialsandFinishes.DoorHandleMaterial char(8), MaterialsandFinishes.DoorMaterial char(13), MaterialsandFinishes.EdgeMaterial char(41), MaterialsandFinishes.FaucetMaterial char(15), MaterialsandFinishes.FrameMaterial char(10), MaterialsandFinishes.GlassPaneMaterial char(5), MaterialsandFinishes.Glazing char(5), MaterialsandFinishes.PanelMaterial char(33), MaterialsandFinishes.SashMaterial char(8), MaterialsandFinishes.ShadeMaterial char(34), MaterialsandFinishes.Toilet-Bowl/BasinMaterial char(16), MaterialsandFinishes.Toilet-SeatMaterial char(22),
      MaterialsandFinishes.TrimMaterial char(13), MaterialsandFinishes.WorkSurfaceMaterial char(28), Mechanical.CWFU number(31,15), Mechanical.HWFU number(31,15), Mechanical.WFU number(31,15), Name char(29), ObjectId number(10,0), Orientation char(13), Other.BalusterLength number(31,15), Other.BalusterSeparation number(31,15), Other.BalusterShape number(10,0), Other.BalusterSpacingType(StairRailingOnly) number(10,0), Other.BalusterWidth number(31,15), Other.BalustersPerTread(StairRailingOnly) number(10,0), Other.BottomHoopHeight number(31,15), Other.BottomHoopRadius number(31,15), Other.CenterDistance number(31,15), Other.ConnectorPos.x1 number(31,15), Other.ConnectorPos.x2 number(31,15), Other.ConnectorPos.y1 number(31,15), Other.ConnectorPos.y2 number(31,15), Other.GuardrailHeight number(31,15), Other.HalfFountainWidth number(31,15), Other.HalfUrinalWidth number(31,15), Other.HalfWallWidth number(31,15), Other.Height1 number(31,15), Other.HookRadius number(31,15), Other.HoopRadius number(31,15), Other.HoopThickness number(31,15), Other.HoopWidth number(31,15),
      Other.None char(1710), Other.PanelWidth number(31,15), Other.R number(31,15), Other.RailShape number(10,0), Other.RailingThickness number(31,15), Other.RailingWidth number(31,15), Other.RungRadius number(31,15), Other.SideRailThickness number(31,15), Other.SideRailWidth number(31,15), Other.VerticalBarCenter number(31,15), Other.VerticalBarCenter1 number(31,15), Other.VerticalBarThickness number(31,15), Other.VerticalBarWidth number(31,15), Other.W number(31,15), Other.WALL_BASE_OFFSET_COMPUTED number(31,15), Other.WALL_FAKE_END_PARAM_0 number(31,15), Other.WALL_FAKE_END_PARAM_1 number(31,15), Other.WALL_HEIGHT_PARAM number(31,15), RoomAreabyDepartment.Area number(31,15), RoomAreabyDepartment.Perimeter number(31,15), RoomAreabyDepartment.RoomNumber char(1), RoomAreabyDepartment.RoomType char(7), Scale char(7), Structural.NumberofCages number(10,0), Structural.NumberofRungs number(10,0), Structural.Structural boolean, Template char(4), TopLevel char(7), TopLevelElevation number(31,15), TopLevelIsStory char(3),
      TopLevelRoomOffset number(31,15), Type char(16), ViewDepth.Level char(29), ViewDepth.Offset number(31,15), ViewRangeBottom.Level char(29), ViewRangeBottom.Offset number(31,15), ViewRangeCutPlane.Level char(29), ViewRangeCutPlane.Offset number(31,15), ViewRangeTop.Level char(29), ViewRangeTop.Offset number(31,15), WorksetName char(8), qa-CaseworkQuantities.AssemblyCode char(8), qa-CaseworkQuantities.AssemblyDescription char(30), qa-CaseworkQuantities.Depth number(31,15), qa-CaseworkQuantities.Height number(31,15), qa-CurtainWallMullionQuantities.Length number(31,15), qa-CurtainWallPanelQuantities.Area number(31,15), qa-CurtainWallPanelQuantities.Height number(31,15), qa-CurtainWallPanelQuantities.Width number(31,15), qa-DoorQuantities.AssemblyCode char(8), qa-DoorQuantities.AssemblyDescription char(32), qa-DoorQuantities.DoorType char(2), qa-DoorQuantities.Height number(31,15), qa-DoorQuantities.Thickness number(31,15), qa-DoorQuantities.Width number(31,15), qa-FloorFinishes.Area number(31,15), qa-FloorFinishes.Perimeter number(31,15), qa-FloorFinishes.RoomNumber char(1), qa-FloorFinishes.RoomType char(7), qa-FurnitureQuantities.AssemblyCode char(8),
      qa-FurnitureQuantities.AssemblyDescription char(23), qa-FurnitureSystemQuantities.Comments char(47), qa-RailingQuantities.Length number(31,15), qa-RoomWallFinishes.Perimeter number(31,15), qa-RoomWallFinishes.RoomNumber char(1), qa-RoomWallFinishes.RoomType char(7), qa-StairQuantities.ActualNumberofRisers number(10,0), qa-StairQuantities.ActualRiserHeight number(31,15), qa-WindowQuantities.AssemblyCode char(8), qa-WindowQuantities.AssemblyDescription char(7), qa-WindowQuantities.Height number(31,15), qa-WindowQuantities.Width number(31,15), qa-WindowQuantities.WindowType char(2), qe-LightingFixtureQuantities.Lamp char(3), qe-LightingFixtureQuantities.Lumens number(31,15), qp-PlumbingFixtureQuantities.AssemblyCode char(8), qp-PlumbingFixtureQuantities.AssemblyDescription char(5), qs-FloorQuantitiesbyAssembly.Area(DefinedByModeler) number(31,15), qs-FloorQuantitiesbyAssembly.Perimeter number(31,15), qs-RoofQuantitiesbyAssembly.Area number(31,15), qs-StructuralBeams&BracingQuantities.AssemblyCode char(3), qs-StructuralBeams&BracingQuantities.AssemblyDescription char(14), qs-StructuralBeams&BracingQuantities.Length number(31,15), qs-StructuralColumnSchedule.AssemblyCode char(3), qs-StructuralColumnSchedule.AssemblyDescription char(14), qs-StructuralColumnSchedule.Length number(31,15), qs-StructuralFramingSchedule.AssemblyCode char(3), qs-StructuralFramingSchedule.AssemblyDescription char(14), qs-StructuralFramingSchedule.Length number(31,15), qs-StructuralFramingSchedule.Volume number(31,15),
      qs-WallQuantitiesbyAssembly.Area number(31,15), qs-WallQuantitiesbyAssembly.Length-CenterToCenter number(31,15), qs-WallQuantitiesbyAssembly.Volume number(31,15)
    -> GeometryFilter
GeometryFilter
    BREAK_AGG = Yes
    GEOM_PORT_NAMES = Surface
    INSTANTIATE = Yes
    SURFACE -> PointCloudCombiner
AttributeKeeper
    -> PointCloudThinner
PointCloudThinner
    INTERVAL = 10
    THINNED -> PointCloudCoercer
PointCloudCoercer
    ACCUM_ATTRS_NAME = Yes
    CONVERT_TO_DISPLAY = Individual Points
    PART_NUMBER_ATTR_NAME = _part_number
    POINT_COMPONENTS = color_red color_green color_blue
    POINT_COMPONENTS_PRESERVE_DISPLAY = Attributes
    COERCED -> CoordinateExtractor
CoordinateExtractor
    IND = 0
    MODE = Specify Coordinate
    X_ATTR = _x
    Y_ATTR = _y
    Z_ATTR = _z
    -> ColorConverter
ColorConverter
    InputAttribute = fme_color
    InputModel = FME
    OutputModel = RGB
    -> File1 (writer CSV2_1)
File1 (writer CSV2_1)
    attributes: x x_coordinate, y y_coordinate, z z_coordinate, r uint8, g uint8, b uint8

Bookmark: Read the RVT file
Architectural.GenericModels (reader REVITNATIVE_1) [off]
    attributes: ObjectId number(10,0), BuildingLevelElevation number(31,15), BuildingLevelRoomOffset number(31,15), BuildingLevelIsStory char(3), BaseCategory char(14), BuildingLevel char(7), Category char(14), Constraints.DefaultElevation number(31,15), CreatedPhase char(16), Dimensions.Height number(31,15), Dimensions.Width number(31,15), Discipline char(13), ElementType char(14), Elevation number(31,15), Family char(13), FamilyType char(13), Function char(8), InExteriorShell char(3), MaterialsandFinishes.BaseMaterial char(29), MaterialsandFinishes.FieldMaterial char(12), MaterialsandFinishes.Lettering char(13), Text.SignText char(9), WorksetName char(40)
    -> PointCloudCombiner
Architectural.Doors (reader REVITNATIVE_1) [off]
    attributes: ObjectId number(10,0), BuildingLevelElevation number(31,15), BuildingLevelRoomOffset number(31,15), BuildingLevelIsStory char(3), AnalyticalProperties.AnalyticConstruction char(5), AnalyticalProperties.ConstructionTypeId char(5), AnalyticalProperties.SolarHeatGainCoefficient number(31,15), AnalyticalProperties.VisualLightTransmittance number(31,15), BaseCategory char(5), BuildingLevel char(7), Category char(5), Construction.Function number(10,0), Construction.WallClosure number(10,0), CreatedPhase char(16), Dimensions.Height number(31,15), Dimensions.Thickness number(31,15), Dimensions.TrimProjectionExt number(31,15), Dimensions.TrimProjectionInt number(31,15), Dimensions.TrimWidth number(31,15), Dimensions.Width number(31,15), Discipline char(13), ElementType char(14), Elevation number(31,15), Family char(12), FamilyType char(9), Function char(8), HostFeatureType char(19), HostId number(10,0), IdentityData.AssemblyCode char(5), IdentityData.AssemblyDescription char(14),
      IdentityData.OmniclassNumber char(11), IdentityData.OmniclassTitle char(5), InExteriorShell char(3), MaterialsandFinishes.DoorMaterial char(12), MaterialsandFinishes.FrameMaterial char(12), WorksetName char(40)
    -> PointCloudCombiner
Architectural.Lines (reader REVITNATIVE_1) [off]
    attributes: ObjectId number(10,0), BuildingLevelElevation number(31,15), BuildingLevelRoomOffset number(31,15), BuildingLevelIsStory char(3), BaseCategory char(5), Category char(5), CreatedPhase char(16), Discipline char(13), ElementType char(9), Family char(0), FamilyType char(0), InExteriorShell char(3), WorksetName char(40)
    -> PointCloudCombiner
Architectural.Planting (reader REVITNATIVE_1) [off]
    attributes: ObjectId number(10,0), BuildingLevelElevation number(31,15), BuildingLevelRoomOffset number(31,15), BuildingLevelIsStory char(3), BaseCategory char(8), BuildingLevel char(7), Category char(8), Constraints.DefaultElevation number(31,15), CreatedPhase char(16), Dimensions.Height number(31,15), Discipline char(13), ElementType char(14), Elevation number(31,15), Family char(20), FamilyType char(22), Function char(8), IdentityData.AssemblyCode char(8), IdentityData.AssemblyDescription char(8), IdentityData.OmniclassNumber char(14), IdentityData.OmniclassTitle char(15), IdentityData.RenderAppearance char(39), IdentityData.RenderAppearanceProperties char(2198), IdentityData.TypeComments char(16), InExteriorShell char(3), WorksetName char(40)
    -> PointCloudCombiner
Architectural.Ramps (reader REVITNATIVE_1) [off]
    attributes: ObjectId number(10,0), BuildingLevelElevation number(31,15), BuildingLevelRoomOffset number(31,15), BuildingLevelIsStory char(3), BaseCategory char(5), Category char(5), Constraints.BaseOffset number(31,15), Constraints.TopOffset number(31,15), CreatedPhase char(16), Dimensions.Width number(31,15), Discipline char(13), ElementType char(4), Family char(0), FamilyType char(6), Graphics.Downarrow boolean, Graphics.Downlabel boolean, Graphics.Downtext char(2), Graphics.ShowUparrowinallviews boolean, Graphics.Uparrow boolean, Graphics.Uplabel boolean, Graphics.Uptext char(0), InExteriorShell char(3), WorksetName char(40)
    -> PointCloudCombiner
Architectural.Roofs (reader REVITNATIVE_1) [off]
    attributes: ObjectId number(10,0), BuildingLevelElevation number(31,15), BuildingLevelRoomOffset number(31,15), BuildingLevelIsStory char(3), BaseCategory char(5), BuildingLevel char(7), Category char(5), Constraints.BaseOffsetFromLevel number(31,15), Constraints.CutoffOffset number(31,15), Construction.FasciaDepth number(31,15), Construction.MaximumRidgeHeight number(31,15), Construction.RafterCut number(10,0), Construction.RafterorTruss number(10,0), CreatedPhase char(16), Discipline char(13), ElementType char(11), Family char(10), FamilyType char(13), Function char(8), IdentityData.AssemblyCode char(5), IdentityData.AssemblyDescription char(17), InExteriorShell char(3), WorksetName char(40)
    -> PointCloudCombiner
Architectural.Site (reader REVITNATIVE_1) [off]
    attributes: ObjectId number(10,0), BuildingLevelElevation number(31,15), BuildingLevelRoomOffset number(31,15), BuildingLevelIsStory char(3), BaseCategory char(4), BuildingLevel char(7), Category char(4), CreatedPhase char(16), Discipline char(13), ElementType char(14), Elevation number(31,15), Family char(15), FamilyType char(15), Function char(8), InExteriorShell char(3), WorksetName char(40)
    -> PointCloudCombiner
Architectural.Topography (reader REVITNATIVE_1) [off]
    attributes: ObjectId number(10,0), BuildingLevelElevation number(31,15), BuildingLevelRoomOffset number(31,15), BuildingLevelIsStory char(3), BaseCategory char(10), Category char(10), CreatedPhase char(16), Discipline char(13), ElementType char(11), Family char(0), FamilyType char(0), InExteriorShell char(3), MaterialsandFinishes.Material char(21), WorksetName char(40)
    -> PointCloudCombiner
Architectural.Walls (reader REVITNATIVE_1) [off]
    attributes: ObjectId number(10,0), BuildingLevelElevation number(31,15), BuildingLevelRoomOffset number(31,15), BuildingLevelIsStory char(3), BaseCategory char(5), BuildingLevel char(7), Category char(5), Constraints.BaseExtensionDistance number(31,15), Constraints.BaseOffset number(31,15), Constraints.TopExtensionDistance number(31,15), Constraints.TopOffset number(31,15), Constraints.UnconnectedHeight number(31,15), CreatedPhase char(16), Discipline char(13), ElementType char(5), Family char(10), FamilyType char(18), Function char(8), IdentityData.AssemblyCode char(5), IdentityData.AssemblyDescription char(14), InExteriorShell char(3), Other.WALL_BASE_OFFSET_COMPUTED number(31,15), Other.WALL_HEIGHT_PARAM number(31,15), WorksetName char(40)
    -> PointCloudCombiner
Architectural.Windows (reader REVITNATIVE_1) [off]
    attributes: ObjectId number(10,0), BuildingLevelElevation number(31,15), BuildingLevelRoomOffset number(31,15), BuildingLevelIsStory char(3), AnalyticalProperties.AnalyticConstruction char(32), AnalyticalProperties.ConstructionTypeId char(5), AnalyticalProperties.SolarHeatGainCoefficient number(31,15), AnalyticalProperties.VisualLightTransmittance number(31,15), BaseCategory char(7), BuildingLevel char(7), Category char(7), Construction.WallClosure number(10,0), CreatedPhase char(16), Dimensions.DefaultSillHeight number(31,15), Dimensions.Height number(31,15), Dimensions.Width number(31,15), Dimensions.WindowInset number(31,15), Discipline char(13), ElementType char(14), Elevation number(31,15), Family char(5), FamilyType char(9), Function char(8), HostFeatureType char(19), HostId number(10,0), IdentityData.AssemblyCode char(8), IdentityData.AssemblyDescription char(7), IdentityData.Mark char(1), IdentityData.OmniclassNumber char(14), IdentityData.OmniclassTitle char(13),
      InExteriorShell char(3), MaterialsandFinishes.GlassPaneMaterial char(5), MaterialsandFinishes.SashMaterial char(4), WorksetName char(40)
    -> PointCloudCombiner
SurveyPoint (reader REVITNATIVE_1) [off]
    -> PointCloudCombiner
Note: Don't feed metadata into PointCloudCombiner: it causes errors.
Metadata.FileInformation (reader REVITNATIVE_1) [off]
    attributes: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
Metadata.ViewInformation (reader REVITNATIVE_1) [off]
    attributes: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

Bookmark: Convert to a point cloud
Note: This isn't extracting color from the RVT file. I've asked on the forums how to do this, and am awaiting a response. As of now, we don't need the colors, but we may want them in the future.
PointCloudCombiner
    ACCUM_ATTRS_NAME = Yes
    EXTRACT_RASTER_NODATA_NAME = No
    SPACING = 1.0
    -> File1 (writer POINTCLOUDXYZ_1)
    -> AttributeKeeper

Bookmark: Write as a point cloud file
File1 (writer POINTCLOUDXYZ_1)

FME custom transformer ColorConverter
Converts color values between different formats (FME
 RGB
 Web RGB and CMYK)
Input:
1 attribute containing a color triplet in either FME, RGB, Web RGB or CMYK format, comma-separated
Output:
Attributes _output_color (full color triplet in the required format), _output_red, output_green and _output_blue
Supported color models:
FME color, RGB values in range 0..1
RGB values in range 0..255
Web RGB values, a hexadecimal string of 6 characters containing an RGB triplet with each value in the range 00..FF
CMYK values in range 0..1 and 0..100
Note that due to rounding errors the resulting colors might be a bit off. Especially any conversions between the RGB and CMYK color spaces might yield results that differ from other applications (since the RGB and CMYK color spaces are slightly different)

Parameters:
- InputAttribute = fme_fill_color   # " " Input color attribute
- InputModel = FME   # RGB"%"CMYK (0..1)"%"CMYK (0..100)" Input color model
- OutputModel = FME   # RGB"%"CMYK (0..1)"%"CMYK (0..100)" Output color model

Input (input)
    -> TestFilter
Note: Select input color model
TestFilter
    DEFAULT_VALUE = <UNFILTERED>
    TEST_LIST = BOOL_OP,OR,COMPOSITE_TEST,<Unused>,TEST_CLAUSE,"TEST $(InputModel) = FME",FME,BOOL_OP,OR,COMPOSITE_TEST,<Unused>,TEST_CLAUSE,"TEST $(InputModel) = RGB",RGB,BOOL_OP,OR,COMPOSITE_TEST,<Unused>,TEST_CLAUSE,"TEST $(InputModel) = Web RGB",Web RGB,BOOL_OP,OR,COMPOSITE_TEST,<Unused>,TEST_CLAUSE,"TEST $(InputModel) = CMYK (0..100)",CMYK (0..100),BOOL_OP,OR,COMPOSITE_TEST,<Unused>,TEST_CLAUSE,"TEST $(InputModel) = CMYK (0..1)",CMYK (0..1)
    FME -> AttributeSplitter
    RGB -> AttributeSplitter_2
    Web RGB -> StringReplacer
    CMYK (0..100) -> AttributeSplitter_5
    CMYK (0..1) -> AttributeSplitter_4
Note: Select output color model
TestFilter_2
    DEFAULT_VALUE = <UNFILTERED>
    TEST_LIST = BOOL_OP,OR,COMPOSITE_TEST,<Unused>,TEST_CLAUSE,"TEST $(OutputModel) = FME",FME,BOOL_OP,OR,COMPOSITE_TEST,<Unused>,TEST_CLAUSE,"TEST $(OutputModel) = RGB",RGB,BOOL_OP,OR,COMPOSITE_TEST,<Unused>,TEST_CLAUSE,"TEST $(OutputModel) = Web RGB",Web RGB,BOOL_OP,OR,COMPOSITE_TEST,<Unused>,TEST_CLAUSE,"TEST $(OutputModel) = CMYK (0..1)",CMYK (0..1),BOOL_OP,OR,COMPOSITE_TEST,<Unused>,TEST_CLAUSE,"TEST $(OutputModel) = CMYK (0..100)",CMYK (0..100)
    FME -> AttributeManager_5
    RGB -> AttributeManager_2
    Web RGB -> AttributeManager_7
    CMYK (0..1) -> AttributeManager_10
    CMYK (0..100) -> AttributeManager_11
Output (output)

Bookmark: FME color triplet
AttributeSplitter
    ATTR_NAME = $(InputAttribute)
    DELIMITER = ,
    DROP_EMPTY_PARTS = No
    LIST_NAME = _list
    TRIM_OPTION = Both
    -> AttributeManager
AttributeManager
    ATTR_TABLE:
      SET_TO _input_red = @Value(_list{0})
      SET_TO _input_green = @Value(_list{1})
      SET_TO _input_blue = @Value(_list{2})
    -> TestFilter_2

Bookmark: RGB color triplet
AttributeSplitter_2
    ATTR_NAME = $(InputAttribute)
    DELIMITER = ,
    DROP_EMPTY_PARTS = No
    LIST_NAME = _list
    TRIM_OPTION = Both
    -> AttributeManager_3
AttributeManager_3
    ATTR_TABLE:
      SET_TO _input_red = @Evaluate(@Value(_list{0})/255)
      SET_TO _input_green = @Evaluate(@Value(_list{1})/255)
      SET_TO _input_blue = @Evaluate(@Value(_list{2})/255)
    -> TestFilter_2

Bookmark: Web RGB (hexadecimal)
StringReplacer
    CASE = NO
    FIND_TEXT = ^#
    NO_MATCH = _FME_NO_OP_
    REGEXP = YES
    SRC_ATTRS = $(InputAttribute)
    -> AttributeSplitter_3
AttributeSplitter_3
    ATTR_NAME = $(InputAttribute)
    DELIMITER = 2s2s2s
    DROP_EMPTY_PARTS = No
    LIST_NAME = _list
    TRIM_OPTION = Both
    -> BaseConverter
BaseConverter
    DBASE = 10
    OBASE = 16
    SRC = _list{0}
    VAL_ATTR = _input_red
    WIDTH = 3
    -> BaseConverter_2
BaseConverter_2
    DBASE = 10
    OBASE = 16
    SRC = _list{1}
    VAL_ATTR = _input_green
    WIDTH = 3
    -> BaseConverter_3
BaseConverter_3
    DBASE = 10
    OBASE = 16
    SRC = _list{2}
    VAL_ATTR = _input_blue
    WIDTH = 3
    -> AttributeManager_4
AttributeManager_4
    ATTR_TABLE:
      SET_TO _input_red = @Evaluate(@Value(_input_red)/255)
      SET_TO _input_green = @Evaluate(@Value(_input_green)/255)
      SET_TO _input_blue = @Evaluate(@Value(_input_blue)/255)
    -> TestFilter_2

Bookmark: CMYK
AttributeSplitter_5
    ATTR_NAME = $(InputAttribute)
    DELIMITER = ,
    DROP_EMPTY_PARTS = No
    LIST_NAME = _list
    TRIM_OPTION = Both
    -> AttributeManager_9
AttributeManager_9
    ATTR_TABLE:
      SET_TO _input_red = @Evaluate((1-(@Value(_list{0})/100))*(1-(@Value(_list{3})/100)))
      SET_TO _input_green = @Evaluate((1-(@Value(_list{1})/100))*(1-(@Value(_list{3})/100)))
      SET_TO _input_blue = @Evaluate((1-(@Value(_list{2})/100))*(1-(@Value(_list{3})/100)))
    -> TestFilter_2
AttributeSplitter_4
    ATTR_NAME = $(InputAttribute)
    DELIMITER = ,
    DROP_EMPTY_PARTS = No
    LIST_NAME = _list
    TRIM_OPTION = Both
    -> AttributeManager_8
AttributeManager_8
    ATTR_TABLE:
      SET_TO _input_red = @Evaluate((1-@Value(_list{0}))*(1-@Value(_list{3})))
      SET_TO _input_green = @Evaluate((1-@Value(_list{1}))*(1-@Value(_list{3})))
      SET_TO _input_blue = @Evaluate((1-@Value(_list{2}))*(1-@Value(_list{3})))
    -> TestFilter_2

Bookmark: FME color triplet
AttributeManager_5
    ATTR_TABLE:
      RENAME_SET_VALUE _input_red > _output_red
      RENAME_SET_VALUE _input_green > _output_green
      RENAME_SET_VALUE _input_blue > _output_blue
      SET_TO _output_color = @Value(_output_red),@Value(_output_green),@Value(_output_blue)
    -> Output (output)

Bookmark: RGB color triplet
AttributeManager_2
    ATTR_TABLE:
      SET_TO _output_red = @Evaluate(@int(@Value(_input_red)*255))
      SET_TO _output_green = @Evaluate(@int(@Value(_input_green)*255))
      SET_TO _output_blue = @Evaluate(@int(@Value(_input_blue)*255))
      SET_TO _output_color = @Value(_output_red),@Value(_output_green),@Value(_output_blue)
    -> Output (output)

Bookmark: Web RGB (hexadecimal
AttributeManager_7
    ATTR_TABLE:
      SET_TO _input_red = @Evaluate(int(@Value(_input_red)*255))
      SET_TO _input_green = @Evaluate(int(@Value(_input_green)*255))
      SET_TO _input_blue = @Evaluate(int(@Value(_input_blue)*255))
    -> BaseConverter_4
    -> AttributeManager_7_Output
BaseConverter_4
    DBASE = 16
    OBASE = 10
    SRC = _input_red
    VAL_ATTR = _output_red
    WIDTH = 2
    -> BaseConverter_5
BaseConverter_5
    DBASE = 16
    OBASE = 10
    SRC = _input_green
    VAL_ATTR = _output_green
    WIDTH = 2
    -> BaseConverter_6
BaseConverter_6
    DBASE = 16
    OBASE = 10
    SRC = _input_blue
    VAL_ATTR = _output_blue
    WIDTH = 2
    -> AttributeManager_6
AttributeManager_6
    ATTR_TABLE = SET_TO _output_color = #@Value(_output_red)@Value(_output_green)@Value(_output_blue)
    -> Output (output)
AttributeManager_7_Output: Inspector

Bookmark: CMYK
AttributeManager_10
    ATTR_TABLE:
      SET_TO _output_key = @Evaluate(1-@max(@Value(_input_red),@Value(_input_green),@Value(_input_blue)))
      SET_TO _output_cyan = @Evaluate((1-@Value(_input_red)-@Value(_output_key))/(1-@Value(_output_key)))
      SET_TO _output_magenta = @Evaluate((1-@Value(_input_green)-@Value(_output_key))/(1-@Value(_output_key)))
      SET_TO _output_yellow = @Evaluate((1-@Value(_input_blue)-@Value(_output_key))/(1-@Value(_output_key)))
    -> AttributeRounder
AttributeManager_11
    ATTR_TABLE:
      SET_TO _output_key = @Evaluate((1-@max(@Value(_input_red),@Value(_input_green),@Value(_input_blue)))*100)
      SET_TO _output_cyan = @Evaluate(((1-@Value(_input_red)-@Value(_output_key))/(1-@Value(_output_key)))*100)
      SET_TO _output_magenta = @Evaluate(((1-@Value(_input_green)-@Value(_output_key))/(1-@Value(_output_key)))*100)
      SET_TO _output_yellow = @Evaluate(((1-@Value(_input_blue)-@Value(_output_key))/(1-@Value(_output_key)))*100)
    -> AttributeRounder
AttributeRounder
    PLACES = 2
    ROUND_TYPE = Nearest
    SRC_ATTRS = _output_cyan _output_key _output_yellow _output_magenta
    -> AttributeManager_12
AttributeManager_12
    ATTR_TABLE = SET_TO _output_color = @Value(_output_cyan),@Value(_output_magenta),@Value(_output_yellow),@Value(_output_key)
    -> Output (output)
