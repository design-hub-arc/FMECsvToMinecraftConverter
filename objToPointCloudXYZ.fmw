FME workspace objToPointCloudXYZ.fmw

Parameters:
- DestDataset_POINTCLOUDXYZ = $(FME_MF_DIR)convertedData   # Destination Point Cloud XYZ Folder
- writtenFileName = objToCsvMTPlane   # enter a name for the written file
- SourceDataset_GENERIC = $(FME_MF_DIR)sourceData\objData\aerospaceMuseumAirplane.obj   # Source Dataset
- FEATURE_TYPES_2 = aerospaceMuseumAirplane

Readers:
- OBJ_1: OBJ from $(FME_MF_DIR)sourceData\objData\AnyConv.com__DESGN100_Sample - 3D View - {3D}.obj
- GENERIC_1: GENERIC from $(SourceDataset_GENERIC)

Writers:
- POINTCLOUDXYZ_1: POINTCLOUDXYZ to $(DestDataset_POINTCLOUDXYZ) in *XY-MT*

NewFeatureType (reader GENERIC_1)
    -> PointCloudCombiner
PointCloudCombiner
    ACCUM_ATTRS_NAME = Yes
    EXTRACT_RASTER_NODATA_NAME = No
    SPACING = 1.0
    -> aerospaceMuseumAirplane (writer POINTCLOUDXYZ_1)
aerospaceMuseumAirplane (writer POINTCLOUDXYZ_1)
