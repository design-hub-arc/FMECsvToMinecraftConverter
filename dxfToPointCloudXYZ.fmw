FME workspace dxfToPointCloudXYZ.fmw

Parameters:
- SourceDataset_ACAD = $(FME_MF_DIR)sourceData\dxfData\DESGN100_Sample - 3D View - {3D}.dxf   # Source Autodesk AutoCAD DWG/DXF File(s)
- DestDataset_POINTCLOUDXYZ = $(FME_MF_DIR)converted   # Destination Point Cloud XYZ Folder
- fileName = fbxToCsvMT   # Enter a name for the converted file

Readers:
- ACAD_1: ACAD from $(SourceDataset_ACAD) in *XY-FT*

Writers:
- POINTCLOUDXYZ_1: POINTCLOUDXYZ to $(DestDataset_POINTCLOUDXYZ) in *XY-MT*

0 (reader ACAD_1)
    -> PointCloudCombiner
A-DETL-WIDE (reader ACAD_1)
    -> PointCloudCombiner
A-DOOR (reader ACAD_1)
    -> PointCloudCombiner
A-DOOR-FRAM (reader ACAD_1)
    -> PointCloudCombiner
A-FLOR-LEVL (reader ACAD_1)
    -> PointCloudCombiner
A-GENM (reader ACAD_1)
    -> PointCloudCombiner
A-GLAZ (reader ACAD_1)
    -> PointCloudCombiner
A-ROOF (reader ACAD_1)
    -> PointCloudCombiner
A-WALL (reader ACAD_1)
    -> PointCloudCombiner
C-BLDG-PADS (reader ACAD_1)
    -> PointCloudCombiner
C-TOPO (reader ACAD_1)
    -> PointCloudCombiner
C-TOPO-MAJR (reader ACAD_1)
    -> PointCloudCombiner
C-TOPO-MINR (reader ACAD_1)
    -> PointCloudCombiner
L-PLNT (reader ACAD_1)
    -> PointCloudCombiner
L-SITE (reader ACAD_1)
    -> PointCloudCombiner
PointCloudCombiner
    ACCUM_ATTRS_NAME = Yes
    EXTRACT_RASTER_NODATA_NAME = No
    SPACING = 1.0
    -> File1 (writer POINTCLOUDXYZ_1)
File1 (writer POINTCLOUDXYZ_1)
