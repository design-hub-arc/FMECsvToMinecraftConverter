FME workspace xyzToCsv.fmw

Parameters:
- SourceDataset_POINTCLOUDXYZ = $(FME_MF_DIR)sourceData\xyzData\points.xyz   # Point Cloud XYZ File(s)
- DestDataset_CSV2 = $(FME_MF_DIR)convertedData   # Destination CSV (Comma Separated Value) Folder
- resultFileName = @Trim(@Value(_filename))   # Enter name for result file

Readers:
- POINTCLOUDXYZ_1: POINTCLOUDXYZ from $(SourceDataset_POINTCLOUDXYZ)

Writers:
- CSV2_1: CSV2 to $(DestDataset_CSV2) in *XY-MT*

PointCloudCoercer
    ACCUM_ATTRS_NAME = Yes
    CONVERT_TO_DISPLAY = Individual Points
    PART_NUMBER_ATTR_NAME = _part_number
    POINT_COMPONENTS_PRESERVE_DISPLAY = Attributes
    COERCED -> CoordinateExtractor
CoordinateExtractor
    IND = 0
    MODE = Specify Coordinate
    X_ATTR = _x
    Y_ATTR = _y
    Z_ATTR = _z
    -> ColorConverter
ColorConverter
    InputAttribute = fme_color
    InputModel = FME
    OutputModel = RGB
    -> FilenamePartExtractor
FilenamePartExtractor
    DIRNAME_ATTR = _dirname
    DIRPATH_ATTR = _dirpath
    EXTENSION_ATTR = _extension
    FULLNAME_ATTR = _filename
    ROOTNAME_ATTR = _rootname
    SRC_ATTR = $(SourceDataset_POINTCLOUDXYZ)
    -> StringReplacer
StringReplacer
    CASE = NO
    FIND_TEXT = .xyz
    NO_MATCH = _FME_NO_OP_
    REGEXP = NO
    REPLACE_TEXT = _xyz
    SRC_ATTRS = _filename
    -> POINTCLOUDXYZ (writer CSV2_1)

Bookmark: Reader Feature Types
POINTCLOUDXYZ (reader POINTCLOUDXYZ_1)
    -> PointCloudCoercer

Bookmark: Writer Feature Types
POINTCLOUDXYZ (writer CSV2_1)
    attributes: x real64, y real64, z real64, r uint8, g uint8, b uint8

FME custom transformer ColorConverter
Converts color values between different formats (FME
 RGB
 Web RGB and CMYK)
Input:
1 attribute containing a color triplet in either FME, RGB, Web RGB or CMYK format, comma-separated
Output:
Attributes _output_color (full color triplet in the required format), _output_red, output_green and _output_blue
Supported color models:
FME color, RGB values in range 0..1
RGB values in range 0..255
Web RGB values, a hexadecimal string of 6 characters containing an RGB triplet with each value in the range 00..FF
CMYK values in range 0..1 and 0..100
Note that due to rounding errors the resulting colors might be a bit off. Especially any conversions between the RGB and CMYK color spaces might yield results that differ from other applications (since the RGB and CMYK color spaces are slightly different)

Parameters:
- InputAttribute = fme_fill_color   # " " Input color attribute
- InputModel = FME   # RGB"%"CMYK (0..1)"%"CMYK (0..100)" Input color model
- OutputModel = FME   # RGB"%"CMYK (0..1)"%"CMYK (0..100)" Output color model

Input (input)
    -> TestFilter
Note: Select input color model
TestFilter
    DEFAULT_VALUE = <UNFILTERED>
    TEST_LIST = BOOL_OP,OR,COMPOSITE_TEST,<Unused>,TEST_CLAUSE,"TEST $(InputModel) = FME",FME,BOOL_OP,OR,COMPOSITE_TEST,<Unused>,TEST_CLAUSE,"TEST $(InputModel) = RGB",RGB,BOOL_OP,OR,COMPOSITE_TEST,<Unused>,TEST_CLAUSE,"TEST $(InputModel) = Web RGB",Web RGB,BOOL_OP,OR,COMPOSITE_TEST,<Unused>,TEST_CLAUSE,"TEST $(InputModel) = CMYK (0..100)",CMYK (0..100),BOOL_OP,OR,COMPOSITE_TEST,<Unused>,TEST_CLAUSE,"TEST $(InputModel) = CMYK (0..1)",CMYK (0..1)
    FME -> AttributeSplitter
    RGB -> AttributeSplitter_2
    Web RGB -> StringReplacer
    CMYK (0..100) -> AttributeSplitter_5
    CMYK (0..1) -> AttributeSplitter_4
Note: Select output color model
TestFilter_2
    DEFAULT_VALUE = <UNFILTERED>
    TEST_LIST = BOOL_OP,OR,COMPOSITE_TEST,<Unused>,TEST_CLAUSE,"TEST $(OutputModel) = FME",FME,BOOL_OP,OR,COMPOSITE_TEST,<Unused>,TEST_CLAUSE,"TEST $(OutputModel) = RGB",RGB,BOOL_OP,OR,COMPOSITE_TEST,<Unused>,TEST_CLAUSE,"TEST $(OutputModel) = Web RGB",Web RGB,BOOL_OP,OR,COMPOSITE_TEST,<Unused>,TEST_CLAUSE,"TEST $(OutputModel) = CMYK (0..1)",CMYK (0..1),BOOL_OP,OR,COMPOSITE_TEST,<Unused>,TEST_CLAUSE,"TEST $(OutputModel) = CMYK (0..100)",CMYK (0..100)
    FME -> AttributeManager_5
    RGB -> AttributeManager_2
    Web RGB -> AttributeManager_7
    CMYK (0..1) -> AttributeManager_10
    CMYK (0..100) -> AttributeManager_11
Output (output)

Bookmark: FME color triplet
AttributeSplitter
    ATTR_NAME = $(InputAttribute)
    DELIMITER = ,
    DROP_EMPTY_PARTS = No
    LIST_NAME = _list
    TRIM_OPTION = Both
    -> AttributeManager
AttributeManager
    ATTR_TABLE:
      SET_TO _input_red = @Value(_list{0})
      SET_TO _input_green = @Value(_list{1})
      SET_TO _input_blue = @Value(_list{2})
    -> TestFilter_2

Bookmark: RGB color triplet
AttributeSplitter_2
    ATTR_NAME = $(InputAttribute)
    DELIMITER = ,
    DROP_EMPTY_PARTS = No
    LIST_NAME = _list
    TRIM_OPTION = Both
    -> AttributeManager_3
AttributeManager_3
    ATTR_TABLE:
      SET_TO _input_red = @Evaluate(@Value(_list{0})/255)
      SET_TO _input_green = @Evaluate(@Value(_list{1})/255)
      SET_TO _input_blue = @Evaluate(@Value(_list{2})/255)
    -> TestFilter_2

Bookmark: Web RGB (hexadecimal)
StringReplacer
    CASE = NO
    FIND_TEXT = ^#
    NO_MATCH = _FME_NO_OP_
    REGEXP = YES
    SRC_ATTRS = $(InputAttribute)
    -> AttributeSplitter_3
AttributeSplitter_3
    ATTR_NAME = $(InputAttribute)
    DELIMITER = 2s2s2s
    DROP_EMPTY_PARTS = No
    LIST_NAME = _list
    TRIM_OPTION = Both
    -> BaseConverter
BaseConverter
    DBASE = 10
    OBASE = 16
    SRC = _list{0}
    VAL_ATTR = _input_red
    WIDTH = 3
    -> BaseConverter_2
BaseConverter_2
    DBASE = 10
    OBASE = 16
    SRC = _list{1}
    VAL_ATTR = _input_green
    WIDTH = 3
    -> BaseConverter_3
BaseConverter_3
    DBASE = 10
    OBASE = 16
    SRC = _list{2}
    VAL_ATTR = _input_blue
    WIDTH = 3
    -> AttributeManager_4
AttributeManager_4
    ATTR_TABLE:
      SET_TO _input_red = @Evaluate(@Value(_input_red)/255)
      SET_TO _input_green = @Evaluate(@Value(_input_green)/255)
      SET_TO _input_blue = @Evaluate(@Value(_input_blue)/255)
    -> TestFilter_2

Bookmark: CMYK
AttributeSplitter_5
    ATTR_NAME = $(InputAttribute)
    DELIMITER = ,
    DROP_EMPTY_PARTS = No
    LIST_NAME = _list
    TRIM_OPTION = Both
    -> AttributeManager_9
AttributeManager_9
    ATTR_TABLE:
      SET_TO _input_red = @Evaluate((1-(@Value(_list{0})/100))*(1-(@Value(_list{3})/100)))
      SET_TO _input_green = @Evaluate((1-(@Value(_list{1})/100))*(1-(@Value(_list{3})/100)))
      SET_TO _input_blue = @Evaluate((1-(@Value(_list{2})/100))*(1-(@Value(_list{3})/100)))
    -> TestFilter_2
AttributeSplitter_4
    ATTR_NAME = $(InputAttribute)
    DELIMITER = ,
    DROP_EMPTY_PARTS = No
    LIST_NAME = _list
    TRIM_OPTION = Both
    -> AttributeManager_8
AttributeManager_8
    ATTR_TABLE:
      SET_TO _input_red = @Evaluate((1-@Value(_list{0}))*(1-@Value(_list{3})))
      SET_TO _input_green = @Evaluate((1-@Value(_list{1}))*(1-@Value(_list{3})))
      SET_TO _input_blue = @Evaluate((1-@Value(_list{2}))*(1-@Value(_list{3})))
    -> TestFilter_2

Bookmark: FME color triplet
AttributeManager_5
    ATTR_TABLE:
      RENAME_SET_VALUE _input_red > _output_red
      RENAME_SET_VALUE _input_green > _output_green
      RENAME_SET_VALUE _input_blue > _output_blue
      SET_TO _output_color = @Value(_output_red),@Value(_output_green),@Value(_output_blue)
    -> Output (output)

Bookmark: RGB color triplet
AttributeManager_2
    ATTR_TABLE:
      SET_TO _output_red = @Evaluate(@int(@Value(_input_red)*255))
      SET_TO _output_green = @Evaluate(@int(@Value(_input_green)*255))
      SET_TO _output_blue = @Evaluate(@int(@Value(_input_blue)*255))
      SET_TO _output_color = @Value(_output_red),@Value(_output_green),@Value(_output_blue)
    -> Output (output)

Bookmark: Web RGB (hexadecimal
AttributeManager_7
    ATTR_TABLE:
      SET_TO _input_red = @Evaluate(int(@Value(_input_red)*255))
      SET_TO _input_green = @Evaluate(int(@Value(_input_green)*255))
      SET_TO _input_blue = @Evaluate(int(@Value(_input_blue)*255))
    -> BaseConverter_4
    -> AttributeManager_7_Output
BaseConverter_4
    DBASE = 16
    OBASE = 10
    SRC = _input_red
    VAL_ATTR = _output_red
    WIDTH = 2
    -> BaseConverter_5
BaseConverter_5
    DBASE = 16
    OBASE = 10
    SRC = _input_green
    VAL_ATTR = _output_green
    WIDTH = 2
    -> BaseConverter_6
BaseConverter_6
    DBASE = 16
    OBASE = 10
    SRC = _input_blue
    VAL_ATTR = _output_blue
    WIDTH = 2
    -> AttributeManager_6
AttributeManager_6
    ATTR_TABLE = SET_TO _output_color = #@Value(_output_red)@Value(_output_green)@Value(_output_blue)
    -> Output (output)
AttributeManager_7_Output: Inspector

Bookmark: CMYK
AttributeManager_10
    ATTR_TABLE:
      SET_TO _output_key = @Evaluate(1-@max(@Value(_input_red),@Value(_input_green),@Value(_input_blue)))
      SET_TO _output_cyan = @Evaluate((1-@Value(_input_red)-@Value(_output_key))/(1-@Value(_output_key)))
      SET_TO _output_magenta = @Evaluate((1-@Value(_input_green)-@Value(_output_key))/(1-@Value(_output_key)))
      SET_TO _output_yellow = @Evaluate((1-@Value(_input_blue)-@Value(_output_key))/(1-@Value(_output_key)))
    -> AttributeRounder
AttributeManager_11
    ATTR_TABLE:
      SET_TO _output_key = @Evaluate((1-@max(@Value(_input_red),@Value(_input_green),@Value(_input_blue)))*100)
      SET_TO _output_cyan = @Evaluate(((1-@Value(_input_red)-@Value(_output_key))/(1-@Value(_output_key)))*100)
      SET_TO _output_magenta = @Evaluate(((1-@Value(_input_green)-@Value(_output_key))/(1-@Value(_output_key)))*100)
      SET_TO _output_yellow = @Evaluate(((1-@Value(_input_blue)-@Value(_output_key))/(1-@Value(_output_key)))*100)
    -> AttributeRounder
AttributeRounder
    PLACES = 2
    ROUND_TYPE = Nearest
    SRC_ATTRS = _output_cyan _output_key _output_yellow _output_magenta
    -> AttributeManager_12
AttributeManager_12
    ATTR_TABLE = SET_TO _output_color = @Value(_output_cyan),@Value(_output_magenta),@Value(_output_yellow),@Value(_output_key)
    -> Output (output)
