FME workspace fbxToPointCloudXYZ.fmw

Parameters:
- DestDataset_POINTCLOUDXYZ = $(FME_MF_DIR)convertedData   # Destination Point Cloud XYZ Folder
- fileName = fbxToCsvMT   # enter a name for the resulting file
- SourceDataset_FBX = $(FME_MF_DIR)sourceData\fbxData\DESGN100_Sample.fbx   # Source FBX File(s)

Readers:
- FBX_1: FBX from $(SourceDataset_FBX) in *XY-FT*

Writers:
- POINTCLOUDXYZ_1: POINTCLOUDXYZ to $(DestDataset_POINTCLOUDXYZ) in *XY-MT*

DESGN100_Sample (reader FBX_1)
    -> GeometryPropertyExtractor
GeometryPropertyExtractor
    EXTRACTTYPE_PARAM = Geometry Name
    GEOM_NAME_FIELD = _geometry_name
    EXTRACTED -> FeatureTypeExtractor
MeshMerger
    ACCUM_INPUT_ATTRS = Use Attributes From One Feature
    MESH -> FeatureTypeExtractor
FeatureTypeExtractor
    DEST_ATTR = _feature_type
    -> PointCloudCombiner
Note: Not currently working
PointCloudCombiner
    ACCUM_ATTRS_NAME = Yes
    EXTRACT_RASTER_NODATA_NAME = No
    SPACING = 1.0
    -> File1 (writer POINTCLOUDXYZ_1)
File1 (writer POINTCLOUDXYZ_1)
